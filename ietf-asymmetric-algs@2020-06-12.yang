module ietf-asymmetric-algs {
  yang-version 1.1;
  namespace "urn:ietf:params:xml:ns:yang:ietf-asymmetric-algs";
  prefix aa;

  organization
    "IETF NETCONF (Network Configuration) Working Group";

  contact
    "WG Web:   <http://datatracker.ietf.org/wg/netconf/>
     WG List:  <mailto:netconf@ietf.org>
     Author:   Eric Voit <mailto:evoit@cisco.com>
     Author:   Kent Watsen <mailto:kent+ietf@watsen.net>
     Author:   Wang Haiguang <wang.haiguang.shieldlab@huawei.com>";

  description
    "This module defines a identities for asymmetric algorithms.
    
     Copyright (c) 2020 IETF Trust and the persons identified
     as authors of the code. All rights reserved.
     Redistribution and use in source and binary forms, with
     or without modification, is permitted pursuant to, and
     subject to the license terms contained in, the Simplified
     BSD License set forth in Section 4.c of the IETF Trust's
     Legal Provisions Relating to IETF Documents
     (https://trustee.ietf.org/license-info).
     This version of this YANG module is part of RFC XXXX
     (https://www.rfc-editor.org/info/rfcXXXX); see the RFC
     itself for full legal notices.
     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.";

  revision 2020-06-12 {
    description
      "Initial version";
    reference
      "RFC XXXX: tbd
       initial draft: draft-voit-rats-trusted-path-routing
       concepts from ietf-asymmetric-algs.yang which did not progress to 
       WGLC in NETCONF.";
  }

  /*****************/
  /*   Features    */
  /*****************/

  feature TPM12 {
    description
      "This feature indicates support for the TPM 1.2 API.";
  }

  feature TPM20 {
    description
      "This feature indicates support for the TPM 2.0 API.";
  }
  
  feature iana {
    description
      "This feature indicates support for the IANA algorithms defined
      in Registry xxxxx";
  }

  /*****************/
  /*  Identities   */
  /*****************/
  
  /*  There needs to be collasping/verification of some of the identity types 
      between the various algorithm types listed below */

  identity asymmetric-algorithm-type {
    description
      "Base identity identityerating various asymmetric key algorithms.";
  }
  
  identity iana-asymmetric-algorithm {
    base asymmetric-algorithm-type;
    description
      "Base identity identityerating various asymmetric key algorithms.";
  }
  
  identity tpm12-asymmetric-algorithm {
    base asymmetric-algorithm-type;
    description
      "Base identity identityerating various asymmetric key algorithms.";
    reference
      "TPM-Main-Part-2-TPM-Structures_v1.2_rev116_01032011.pdf
      TPM_ALGORITHM_ID values, page 18";
  }
  
  identity tpm2-asymmetric-algorithm {
    base asymmetric-algorithm-type;
    description
      "Base identity identityerating various asymmetric key algorithms.";
    reference  
      "TPM-Rev-2.0-Part-2-Structures-01.38.pdf
      The TCG Algorithm Registry ID value. Table 9";
  } 
  
  identity rsa {
    base tpm12-asymmetric-algorithm;  
    base tpm2-asymmetric-algorithm;
    description
      "RFC 3447 - the RSA algorithm";
  }
  
  identity rsa1024 {
    if-feature "iana";
    base iana-asymmetric-algorithm;
    base rsa;
    description
      "The RSA algorithm using a 1024-bit key.";
    reference
      "RFC 8017: PKCS #1: RSA Cryptography Specifications Version 2.2.";
      }
      
  identity rsa2048 {
    if-feature "iana";
    base iana-asymmetric-algorithm;
    base rsa;
    description
      "The RSA algorithm using a 2048-bit key.";
    reference
      "RFC 8017: PKCS #1: RSA Cryptography Specifications Version 2.2.";
      }
    
  identity rsa3072 {
    if-feature "iana";
    base iana-asymmetric-algorithm;
    base rsa;
    description
      "The RSA algorithm using a 3072-bit key.";
    reference
      "RFC 8017: PKCS #1: RSA Cryptography Specifications Version 2.2.";
  }

  identity rsa4096 {
    if-feature "iana";
    base iana-asymmetric-algorithm;
    base rsa;
    description
      "The RSA algorithm using a 4096-bit key.";
    reference
      "RFC 8017: PKCS #1: RSA Cryptography Specifications Version 2.2.";
  }
  
  identity rsa7680 {
    if-feature "iana";
    base iana-asymmetric-algorithm;
    base rsa;
    description
      "The RSA algorithm using a 7680-bit key.";
    reference
      "RFC 8017: PKCS #1: RSA Cryptography Specifications Version 2.2.";
  }
  
  identity rsa15360 {
    if-feature "iana";
    base iana-asymmetric-algorithm;
    base rsa;
    description
      "The RSA algorithm using a 15360-bit key.";
    reference
      "RFC 8017: PKCS #1: RSA Cryptography Specifications Version 2.2.";
  }
  
  identity secp192r1 {
    if-feature "iana";
    base iana-asymmetric-algorithm;
    description
      "The asymmetric algorithm using a NIST P192 Curve.";
    reference
      "RFC 6090: Fundamental Elliptic Curve Cryptography Algorithms.
       RFC 5480: Elliptic Curve Cryptography Subject Public Key
                 Information.";
  }

  identity secp224r1 {
    if-feature "iana";
    base iana-asymmetric-algorithm;
    description
      "The asymmetric algorithm using a NIST P224 Curve.";
    reference
      "RFC 6090: Fundamental Elliptic Curve Cryptography Algorithms.
       RFC 5480: Elliptic Curve Cryptography Subject Public Key
                 Information.";
  }

  identity secp256r1 {
    if-feature "iana";
    base iana-asymmetric-algorithm;
    description
      "The asymmetric algorithm using a NIST P256 Curve.";
    reference
      "RFC 6090: Fundamental Elliptic Curve Cryptography Algorithms.
       RFC 5480: Elliptic Curve Cryptography Subject Public Key
                 Information.";
  }
  
  identity secp384r1 {
    base iana-asymmetric-algorithm;
    description
      "The asymmetric algorithm using a NIST P384 Curve.";
    reference
      "RFC 6090: Fundamental Elliptic Curve Cryptography Algorithms.
       RFC 5480: Elliptic Curve Cryptography Subject Public Key
                 Information.";
  }
      
  identity secp521r1 {
    if-feature "iana";
    base iana-asymmetric-algorithm;
    description
      "The asymmetric algorithm using a NIST P521 Curve.";
    reference
      "RFC 6090: Fundamental Elliptic Curve Cryptography Algorithms.
       RFC 5480: Elliptic Curve Cryptography Subject Public Key
                 Information.";
  }
    
  identity x25519 {
    if-feature "iana";
    base iana-asymmetric-algorithm;
    description
      "The asymmetric algorithm using a x.25519 Curve.";
    reference
      "RFC 7748: Elliptic Curves for Security.";
  }
  
  identity x448 {
    if-feature "iana";
    base iana-asymmetric-algorithm;
    description
      "The asymmetric algorithm using a x.448 Curve.";
    reference
      "RFC 7748: Elliptic Curves for Security.";
  }

  identity SHA1 {
    if-feature "TPM20 or TPM12"; 
    base tpm12-asymmetric-algorithm;
    base tpm2-asymmetric-algorithm;
    description
      "ISO/IEC 10118-3 - SHA1 algorithm";
  }
  
  identity HMAC {
    if-feature "TPM20 or TPM12";    
    base tpm12-asymmetric-algorithm;
    base tpm2-asymmetric-algorithm;
    description
      "ISO/IEC 9797-2 - Hash Message Authentication Code (HMAC) algorithm
      also RFC2014.
      we need to verify if NMAC implementation isn't different in the two.";
  }
      
  identity AES {
    if-feature "TPM20 or TPM12"; 
    base tpm2-asymmetric-algorithm;
    description
      "ISO/IEC 18033-3 - the AES algorithm";
  }

  identity AES128 {
    if-feature "TPM12"; 
    base tpm12-asymmetric-algorithm;
    base AES;
    description
      "ISO/IEC 18033-3 - the AES algorithm, key size 128";
  }

  identity AES192 {
    if-feature "TPM12"; 
    base tpm12-asymmetric-algorithm;
    base AES;
    description
      "ISO/IEC 18033-3 - the AES algorithm, key size 192";
  }

  identity AES256 {
    if-feature "TPM12"; 
    base tpm12-asymmetric-algorithm;
    base AES;
    description
      "ISO/IEC 18033-3 - the AES algorithm, key size 256";
  }
      
  identity MGF1 {
    if-feature "TPM20"; 
    base tpm2-asymmetric-algorithm;
    description
      "IEEE Std 1363a -2004 - hash-based mask-generation function";
  }
  identity KEYEDHASH {
    if-feature "TPM20"; 
    base tpm2-asymmetric-algorithm;
    description
      "TPM2 KEYEDHASH - an encryption or signing algorithm using a keyed hash";
    }

  identity XOR {
    if-feature "TPM20 or TPM12"; 
    base tpm12-asymmetric-algorithm;
    base tpm2-asymmetric-algorithm;
    description
        "TPM2 XOR";
  }

  identity SHA256 {
    if-feature "TPM20"; 
    base tpm2-asymmetric-algorithm;
    description
      "ISO/IEC 10118-3 - the SHA 256 algorithm";
  }

  identity SHA384 {
    if-feature "TPM20"; 
    base tpm2-asymmetric-algorithm;
    description
      "ISO/IEC 10118-3 - the SHA 384 algorithm";
  }

  identity SHA512 {
    if-feature "TPM20"; 
    base tpm2-asymmetric-algorithm;
    description
      "ISO/IEC 10118-3 - the SHA 512 algorithm";
  }

  identity NULL {
    if-feature "TPM20"; 
    base tpm2-asymmetric-algorithm;
    description
      "TPM2 NULL";
  }

  identity SM3_256 {
    if-feature "TPM20"; 
    base tpm2-asymmetric-algorithm;
    description
      "GM/T 0004-2012 - SM3_256";
  }

  identity SM4 {
    if-feature "TPM20"; 
    base tpm2-asymmetric-algorithm;
    description
      "GM/T 0004-2012 - SM4 symmetric block cipher";
  }

  identity RSASSA {
    if-feature "TPM20"; 
    base tpm2-asymmetric-algorithm;
    description
      "RFC 3447 - defined in section 8.2 (RSASSAPKCS1-v1_5)";
  }

  identity RSAES {
    if-feature "TPM20"; 
    base tpm2-asymmetric-algorithm;
    description
      "RFC 3447 - defined in section 7.2 (RSAES-PKCS1-v1_5)";
  }

  identity RSAPSS {
    if-feature "TPM20"; 
    base tpm2-asymmetric-algorithm;
    description
      "RFC 3447 - defined in section 8.1 (RSASSA PSS)";
  }

  identity OAEP {
    if-feature "TPM20"; 
    base tpm2-asymmetric-algorithm;
    description
      "RFC 3447 - defined in section 7.1 (RSASSA OAEP)";
  }

  identity ECDSA {
    if-feature "TPM20"; 
    base tpm2-asymmetric-algorithm;
    description
      "ISO/IEC 14888-3 - elliptic curve cryptography (ECC)";
  }            

  identity ECDH {
    if-feature "TPM20"; 
    base tpm2-asymmetric-algorithm;
    description
      "NIST SP800-56A - secret sharing using ECC";
  }

  identity ECDAA {
    if-feature "TPM20"; 
    base tpm2-asymmetric-algorithm;
    description
      "TPM2 - elliptic-curve based anonymous signing scheme";
  }

  identity SM2 {
    if-feature "TPM20"; 
    base tpm2-asymmetric-algorithm;
    description
      "A GM/T 0003.1–2012, GM/T 0003.2–2012, GM/T 0003.3–2012,
      GM/T 0003.5–2012   SM2";
  }

  identity ECSCHNORR {
    if-feature "TPM20"; 
    base tpm2-asymmetric-algorithm;
    description
      "TPM2 - elliptic-curve based Schnorr signature";
  }

  identity ECMQV {
    if-feature "TPM20"; 
    base tpm2-asymmetric-algorithm;
    description
      "NIST SP800-56A - two-phase elliptic-curve key";
  }

  identity KDF1_SP800_56A {
    if-feature "TPM20"; 
    base tpm2-asymmetric-algorithm;
    description
      "NIST SP800-56A - concatenation key derivation function,
      (approved alternative1) section 5.8.1";
  }

  identity KDF2 {
    if-feature "TPM20"; 
    base tpm2-asymmetric-algorithm;
    description
      "IEEE 1363a-2004 - key derivation function KDF2 section 13.2";
  }

  identity KDF1_SP800_108 {
    if-feature "TPM20"; 
    base tpm2-asymmetric-algorithm;
    description
      "NIST SP800-108 - Section 5.1 KDF in Counter Mode";
  }            

  identity ECC {
    if-feature "TPM20"; 
    base tpm2-asymmetric-algorithm;
    description
      "ISO/IEC 15946-1 - prime field ECC";
  }

  identity SYMCIPHER {
    if-feature "TPM20"; 
    base tpm2-asymmetric-algorithm;
    description
      "TPM2 - object type for a symmetric block cipher";
  }            

  identity CAMELLIA {
    if-feature "TPM20"; 
    base tpm2-asymmetric-algorithm;
    description
      "ISO/IEC 18033-3 - the  Camellia algorithm";
  }

  identity CTR {
    if-feature "TPM20"; 
    base tpm2-asymmetric-algorithm;
    description
      "ISO/IEC 10116 - Counter mode";
  }

  identity OFB {
    if-feature "TPM20"; 
    base tpm2-asymmetric-algorithm;
    description
      "ISO/IEC 10116 - Output Feedback mode";
  }

  identity CBC {
    if-feature "TPM20"; 
    base tpm2-asymmetric-algorithm;
    description
      "ISO/IEC 10116 - Cipher Block Chaining mode";
  }

  identity CFB {
    if-feature "TPM20"; 
    base tpm2-asymmetric-algorithm;
    description
      "ISO/IEC 10116 - Cipher Feedback mode";
  }

  identity ECB {
    if-feature "TPM20"; 
    base tpm2-asymmetric-algorithm;
    description
      "ISO/IEC 10116 - Electronic Codebook mode";
  }

}
